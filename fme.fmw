FME workspace fme.fmw

Parameters:
- SourceDataset_SHAPEFILE = ""C:\cwiczenie4_bazydanych\T2019_KAR_POI_TABLE.shp" "C:\cwiczenie4_bazydanych\T2019_KAR_STREET_NODE.shp" "C:\cwiczenie4_bazydanych\T2019_KAR_STREETS.shp""   # Source Esri Shapefile(s)
- SourceDataset_CSV2 = C:\cwiczenie4_bazydanych\routePoints.csv   # Source CSV (Comma Separated Value) File(s)
- SourceDataset_SHAPEFILE_3 = C:\cwiczenie4_bazydanych\T2019_KAR_STREETS.shp   # Source Esri Shapefile(s)
- DestDataset_GEOJSON = $(FME_MF_DIR)cwiczenie8.json   # Destination GeoJSON File
- DestDataset_GEODATABASE_FILE_3 = $(FME_MF_DIR)bezkosztów.gdb   # File Geodatabase
- DestDataset_GEODATABASE_FILE = $(FME_MF_DIR)zkosztami.json   # File Geodatabase

Readers:
- SHAPEFILE_1: SHAPEFILE from $(SourceDataset_SHAPEFILE)
- CSV2_1: CSV2 from $(SourceDataset_CSV2)
- SHAPEFILE_2: SHAPEFILE from $(SourceDataset_SHAPEFILE_3)

Writers:
- GEOJSON_1: GEOJSON to $(DestDataset_GEOJSON)
- GEODATABASE_FILE_1: GEODATABASE_FILE to $(DestDataset_GEODATABASE_FILE)
- GEODATABASE_FILE_2: GEODATABASE_FILE to $(DestDataset_GEODATABASE_FILE_3)

CSV (reader CSV2_1)
    attributes: x x_coordinate, y y_coordinate
    -> VertexCreator
VertexCreator
    CLOSE_LINES = Yes
    IGNORE_DUPLICATES = No
    MEASURE_TYPE = Continuous
    MISSING_VAL_MODE = Compute
    MODE_NAME = Add Point
    XVAL = @Value(x)
    YVAL = @Value(y)
    -> LineBuilder
LineBuilder
    ACCUM_INPUT_ATTRS = Use Attributes From One Feature
    REMOVE_DUPLICATES = NO
    LINE -> Reprojector_2
Reprojector_2
    DEST = DHDN.Berlin/Cassini
    INTERPOLATION_TYPE_NAME = Nearest Neighbor
    RASTER_CELL_SIZE = Preserve Cells
    RASTER_TOLERANCE = 0.0
    SOURCE = EPSG:4326
    REPROJECTED -> ShortestPathFinder [FROM-TO]
    REPROJECTED -> ShortestPathFinder_2 [FROM-TO]
T2019_KAR_POI_TABLE (reader SHAPEFILE_1)
    attributes: POI_ID long, LINK_ID long, TYPE varchar(250), POI_NAME varchar(250), ST_NAME varchar(250), LAT number(31,15), LON number(31,15)
    -> Reprojector
Reprojector
    DEST = DHDN.Berlin/Cassini
    INTERPOLATION_TYPE_NAME = Nearest Neighbor
    RASTER_CELL_SIZE = Preserve Cells
    RASTER_TOLERANCE = 0.0
    SOURCE = EPSG:4326
    REPROJECTED -> SpatialFilter [Candidate]
    REPROJECTED -> SpatialFilter_2 [Candidate]
T2019_KAR_STREETS (reader SHAPEFILE_2)
    attributes: LINK_ID long, ST_NAME varchar(254), REF_IN_ID long, NREF_IN_ID long, FUNC_CLASS varchar(1), SPEED_CAT varchar(1), FR_SPEED_L long, TO_SPEED_L long, DIR_TRAVEL varchar(1)
    -> Reprojector_3
Reprojector_3
    DEST = DHDN.Berlin/Cassini
    INTERPOLATION_TYPE_NAME = Nearest Neighbor
    RASTER_CELL_SIZE = Preserve Cells
    RASTER_TOLERANCE = 0.0
    SOURCE = EPSG:4326
    REPROJECTED -> ShortestPathFinder [NETWORK]
    REPROJECTED -> Tester
    REPROJECTED -> Reprojector_3_Reprojected
Tester
    BOOL_OP = OR
    TEST_CLAUSE:
      TEST @Value(DIR_TRAVEL) = B
      TEST @Value(DIR_TRAVEL) = T
    TEST_MODE = TEST
    PASSED -> AttributeManager
    FAILED -> AttributeManager_2
AttributeManager
    ATTR_TABLE:
      SET_TO FORWARD_COST = 1
      SET_TO REVERSE_COST = 1
    -> ShortestPathFinder_2 [NETWORK]
AttributeManager_2
    ATTR_TABLE:
      SET_TO FORWARD_COST = 1
      SET_TO REVERSE_COST = 9999
    -> ShortestPathFinder_2 [NETWORK]
ShortestPathFinder_2
    ALLOW_UTURNS = Yes
    REORDER_CHOICE = None
    SNAP_POINTS = Yes
    SNAP_TOLERANCE = 200
    WEIGHT_ATTR_1 = FORWARD_COST
    WEIGHT_ATTR_2 = REVERSE_COST
    WEIGHT_ATTR_CHOICE = BY_TWO_ATTRIBUTES
    PATH -> Bufferer_2
    PATH -> PointOnLineOverlayer [LINE]
    PATH -> LengthCalculator
LengthCalculator
    DIM = 2
    LEN_ATTR = _length
    MULT = 1
    -> FeatureMerger [SUPPLIER]
Bufferer_2
    ANGLE = 22.5
    CAP_STYLE = Arc
    CORNER_STYLE = Arc
    MODE = AREA
    OFFSET = 5
    OFFSET_UNITS = METERS
    PRECISION = APPROX
    BUFFERED -> SpatialFilter_2 [Filter]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> punkty_przy_drodze (writer GEOJSON_1)
Reprojector_3_Reprojected: Inspector
ShortestPathFinder
    ALLOW_UTURNS = Yes
    REORDER_MODE = NONE
    SNAP_POINTS = Yes
    SNAP_TOLERANCE = 200
    WEIGHT_ATTR_CHOICE = BY_LENGTH
    PATH -> Bufferer
    PATH -> PointOnLineOverlayer_2 [LINE]
    PATH -> LengthCalculator_2
Bufferer
    ANGLE = 22.5
    CAP_STYLE = Arc
    CORNER_STYLE = Arc
    MODE = AREA
    OFFSET = 5
    OFFSET_UNITS = METERS
    PRECISION = APPROX
    BUFFERED -> SpatialFilter [Filter]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> punkty_przy_drodze (writer GEOJSON_1)
punkty_przy_drodze (writer GEOJSON_1)
    attributes: POI_ID int, LINK_ID int, TYPE string, POI_NAME string, ST_NAME string, LAT float, LON float
LengthCalculator_2
    DIM = 2
    LEN_ATTR = _length
    MULT = 1
    -> FeatureMerger_2 [SUPPLIER]
T2019_KAR_STREET_NODE (reader SHAPEFILE_1)
    attributes: NODE_ID long, LINK_ID long, POINT_NUM long, Z_LEVEL long, INTERSECT varchar(1), LAT number(31,15), LON number(31,15)
    -> Reprojector_4
Reprojector_4
    DEST = DHDN.Berlin/Cassini
    INTERPOLATION_TYPE_NAME = Nearest Neighbor
    RASTER_CELL_SIZE = Preserve Cells
    RASTER_TOLERANCE = 0.0
    SOURCE = EPSG:4326
    REPROJECTED -> PointOnLineOverlayer [POINT]
    REPROJECTED -> PointOnLineOverlayer_2 [POINT]
    REPROJECTED -> Reprojector_4_Reprojected
PointOnLineOverlayer
    DEAGGREGATE_INPUT = Yes
    MEASURE_TYPE = Continuous
    MERGE_MEASURES = Yes
    OV_ATTR = _overlaps
    TOLERANCE = 0
    POINT -> Tester_2
Tester_2
    BOOL_OP = OR
    TEST_CLAUSE = TEST @Value(_overlaps) = 1
    TEST_MODE = TEST
    PASSED -> StatisticsCalculator
StatisticsCalculator
    CALCULATION_MODE = NUMERIC
    FEAT_STATS = LAT,NUMERIC_MODE,MIN,MAX,,SUM,MEAN,MEDIAN,,,,,,,;LON,NUMERIC_MODE,MIN,MAX,,SUM,MEAN,MEDIAN,,,,,,,
    COMPLETE -> FeatureMerger [REQUESTOR]
FeatureMerger
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> zkosztami (writer GEODATABASE_FILE_1)
zkosztami (writer GEODATABASE_FILE_1)
    attributes: NODE_ID integer, LINK_ID integer, POINT_NUM integer, Z_LEVEL integer, INTERSECT char(1), LAT double(31,15), LON double(31,15)
Reprojector_4_Reprojected: Inspector
PointOnLineOverlayer_2
    DEAGGREGATE_INPUT = Yes
    MEASURE_TYPE = Continuous
    MERGE_MEASURES = Yes
    OV_ATTR = _overlaps
    TOLERANCE = 0
    POINT -> Tester_3
Tester_3
    BOOL_OP = OR
    TEST_CLAUSE = TEST @Value(_overlaps) = 1
    TEST_MODE = TEST
    PASSED -> StatisticsCalculator_2
StatisticsCalculator_2
    CALCULATION_MODE = NUMERIC
    FEAT_STATS = LAT,NUMERIC_MODE,MIN,MAX,,SUM,MEAN,MEDIAN,,,,,,,;LON,NUMERIC_MODE,MIN,MAX,,SUM,MEAN,MEDIAN,,,,,,,
    COMPLETE -> FeatureMerger_2 [REQUESTOR]
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> bezkosztow (writer GEODATABASE_FILE_2)
    MERGED -> FeatureMerger_2_Merged
    UNMERGED_REQUESTOR -> FeatureMerger_2_UnmergedRequestor
    USED_SUPPLIER -> FeatureMerger_2_UsedSupplier
    UNUSED_SUPPLIER -> FeatureMerger_2_UnusedSupplier
    <REJECTED> -> FeatureMerger_2__Rejected_
FeatureMerger_2_Merged: Inspector
bezkosztow (writer GEODATABASE_FILE_2)
    attributes: NODE_ID integer, LINK_ID integer, POINT_NUM integer, Z_LEVEL integer, INTERSECT char(1), LAT double(31,15), LON double(31,15)
FeatureMerger_2_UnmergedRequestor: Inspector
FeatureMerger_2_UsedSupplier: Inspector
FeatureMerger_2_UnusedSupplier: Inspector
FeatureMerger_2__Rejected_: Inspector
